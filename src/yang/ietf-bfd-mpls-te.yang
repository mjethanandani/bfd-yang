module ietf-bfd-mpls-te {
  namespace "urn:ietf:params:xml:ns:yang:ietf-bfd-mpls-te";
  // replace with IANA namespace when assigned
  prefix "bfd-mpls-te";
  import ietf-bfd {
    prefix "bfd";
  }
  import ietf-bfd-mpls {
    prefix "bfd-mpls";
  }
  import ietf-te {
    prefix "te";
  }
  organization "IETF BFD Working Group";
  contact
    "WG Web:   <http://tools.ietf.org/wg/bfd>
     WG List:  <rtg-bfd@ietf.org>
     WG Chair: Jeff Haas
     WG Chair: Reshad Rahman
     Editor:   Lianshu Zheng and Reshad Rahman";
  description
    "This module contains the YANG definition for BFD parameters for
     MPLS Traffic Engineering as per RFC5884.";
  revision 2016-02-04 {
    description "Initial revision.";
    reference "RFC XXXX: A YANG data model for BFD over MPLS-TE";
  }
  augment "/bfd:bfd" {
    description "BFD augmentation for MPLS-TE";
    container mpls-te {
      description "BFD MPLS-TE top level container";
      container config {
        description "BFD MPLS-TE configuration container";
        container egress {
          description "Egress configuration";
          uses bfd:bfd-grouping-base-cfg-parms;
          uses bfd:bfd-auth-parms;
        }
      }
      container oper {
        config "false";
        description "BFD operational container";
        uses bfd:bfd-session-statistics;
      }
    }
  }
  augment "/te:te/te:tunnels/te:tunnel/te:config" {
    description "BFD configuration on MPLS-TE tunnel.";
    uses bfd:bfd-grouping-common-cfg-parms;
    uses bfd-mpls:bfd-encap-cfg;
  }
  augment "/te:te/te:lsps-state/te:lsp" {
    when "/te:te/te:lsps-state/te:lsp/te:origin-type != 'transit'" {
      description "BFD information not needed at transit points";
    }
    description "BFD state information on MPLS-TE LSP.";
    uses bfd:bfd-all-session;
    uses bfd-mpls:bfd-mpls-dest-address;
  }
  notification bfd-mpls-te-notification {
    description
      "Notification for BFD over MPLS-TE session state change. " +
      "An implementation may rate-limit notifications, e.g. when a" +
      "session is continuously changing state.";
    uses bfd:bfd-notification-parms;
    uses bfd-mpls:bfd-mpls-dest-address;
    leaf tunnel-name {
      type string;
      description "MPLS-TE tunnel on which BFD was running.";
    }
  }
}
